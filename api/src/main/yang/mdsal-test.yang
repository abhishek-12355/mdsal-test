module mdsal-test {
    yang-version 1;
    namespace "urn:com:netshell:mdsal:params:xml:ns:yang:mdsal-test";
    prefix "mdsal-test";

    revision "2015-01-05" {
        description "Initial revision of mdsal-test model";
    }

    grouping "student" {
        leaf "name" {
            type string;
            config false;
        }

        leaf "sex" {
            config false;
            type enumeration {
                enum "Male" {
                    value 0;
                    description
                        "Male student";
                }

                enum "Female" {
                    value 1;
                    description
                        "Female student";
                }
            }
        }
    }

    container "student-container" {
        uses "student";
    }

    rpc "say-hello" {
     description
        "Say Hello";
        input {
            leaf name {
                type string;
            }
        }
        output {
            leaf response {
                type string;
            }
        }
    }

    rpc "save-student" {
        description
            "Save a new Student";
        input {
            uses "student";
        }
    }

    rpc "get-student" {
        description
            "Retreive Student";
        input {
            leaf "name" {
                type string;
            }
        }

        output {
            uses "student";
        }
    }
}
